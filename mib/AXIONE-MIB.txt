AXIONE-MIB DEFINITIONS ::= BEGIN

IMPORTS
		OBJECT-TYPE, enterprises, MODULE-IDENTITY, Integer32, Counter64
			FROM SNMPv2-SMI

		OBJECT-GROUP, MODULE-COMPLIANCE 
			FROM SNMPv2-CONF

		TEXTUAL-CONVENTION, DisplayString
			FROM SNMPv2-TC
;



axione-mib MODULE-IDENTITY
	LAST-UPDATED 	"201309240000Z"
	ORGANIZATION 	" axione "
	CONTACT-INFO 	"
		Author: Axione STN2 Simon RECHER
		www.axione.fr"

	DESCRIPTION 	"MIB Axione."
	
	
	REVISION 	"201309240000Z"
	DESCRIPTION 	"Ajout de baculaTotalClientsErrors"
	
	REVISION 	"201309100000Z"
	DESCRIPTION 	"Ajout de baculaClientTotalBackup et de baculaClientTotalNumberFile"
	
	REVISION 	"201308230000Z"
	DESCRIPTION 	"Suppression de baculaClientsErrorTable et ajout d'un flag error dans baculaClientsTable "
	
	REVISION 	"201308200000Z"
	DESCRIPTION 	"Ajout de baculaClientsTable et baculaClientsErrorTable"
	
	REVISION 	"201308140000Z"
	DESCRIPTION 	"MIB Axione creation"

	::={ enterprises 33923 }
	-- {{{ Textual conventions
		-- {{{ CounterIndex
		CounterIndex                       ::= TEXTUAL-CONVENTION
			DISPLAY-HINT                     "d"
			STATUS                           current
			DESCRIPTION                      "A unique value, greater than zero, for each type of
											counter in the managed system. It is recommended that
											values are assigned contiguously starting from 1.
											The value for each counter sub-layer must remain
											constant at least from one re-initialization of the
											entity's network management system to the next
											re-initialization."
			SYNTAX                            Integer32 (0..2147483647)
		-- CounterIndex }}}
		-- {{{ TrueFalse
		TrueFalse							::= TEXTUAL-CONVENTION
			STATUS							current
			DESCRIPTION						"True or False values:
											  false - 0
											  true  - 1"
			SYNTAX							INTEGER {
											 false(0),
											 true(1)
										   }
		-- TrueFalse}}
	-- Textual conventions }}}
	
	
	
	--{{{ .1.3.6.1.4.1.33923.0 conformance
	conformance				 OBJECT IDENTIFIER ::= { axione-mib 0 }
		-- {{{ .1.3.6.1.4.1.33923.0.1 baculaConformance
		baculaConformance		OBJECT IDENTIFIER ::= { conformance 1 }
			-- {{{ .1.3.6.1.4.1.33923.0.1.1 baculaCompliance
			baculaCompliance			MODULE-COMPLIANCE
				STATUS					current
				DESCRIPTION				"The compliance statement for SNMP entities which have
										bacula status counters."
				MODULE			-- this module
				MANDATORY-GROUPS			{ baculaGroupClients }
				::= { baculaConformance 1 }
			-- .1.3.6.1.4.1.33923.0.1.1 baculaCompliance }}}
			-- {{{ .1.3.6.1.4.1.33923.0.1.2 baculaGroups
			baculaGroups		 OBJECT IDENTIFIER ::= { baculaConformance 2 }
				--{{{ .1.3.6.1.4.1.33923.0.1.2.1 baculaGroupClients
				baculaGroupClients		OBJECT-GROUP
					OBJECTS				{ baculaVersion, baculaTotalClients, baculaTotalClientsErrors,  
										baculaClientName, baculaClientError, baculaClientSizeBackup, baculaClientTotalSizeBackup, baculaClientNumberFiles, baculaClientTotalNumberFiles }
					STATUS				current
					DESCRIPTION			"A collection of objects providing information
										applicable to Bacula statistics."
					::= { baculaGroups 1 }
				--  .1.3.6.1.4.1.33923.0.1.2.1 baculaGroupClients }}}
			-- .1.3.6.1.4.1.33923.0.1.2 baculaGroups }}}
		-- .1.3.6.1.4.1.33923.0.1 baculaConformance }}}
	-- .1.3.6.1.4.1.33923.0 conformance }}}

	-- {{{ .1.3.6.1.4.1.33923.1 BaculaStats 
	baculaStats 		OBJECT IDENTIFIER ::= { axione-mib 1 }
		-- {{{ .1.3.6.1.4.1.33923.1.1 baculaVersion
		baculaVersion 		OBJECT-TYPE
			SYNTAX 			OCTET STRING -- le sousObjet bacula-version est de type chaine de caractere
			MAX-ACCESS 		read-only -- acces en lecture
			STATUS 			current
			DESCRIPTION		"Version du Director de bacula"
			::= { baculaStats 1 } -- parent du sousObjet
		-- .1.3.6.1.4.1.33923.1.1 baculaVersion }}}
		-- {{{ .1.3.6.1.4.1.33923.1.2 baculaTotalClients
		baculaTotalClients 	OBJECT-TYPE
			SYNTAX 			Integer32 -- le sousObjet bacula-version est de type entier
			MAX-ACCESS 		read-only -- acces en lecture
			STATUS 			current
			DESCRIPTION		"Nombre de client bacula"
			::= { baculaStats 2 } -- parent du sousObjet
		-- .1.3.6.1.4.1.33923.1.2 baculaTotalClients }}}
		-- {{{ .1.3.6.1.4.1.33923.1.3 baculaTotalClientsErrors
		baculaTotalClientsErrors 	OBJECT-TYPE
			SYNTAX 			Integer32 -- le sousObjet bacula-version est de type entier
			MAX-ACCESS 		read-only -- acces en lecture
			STATUS 			current
			DESCRIPTION		"Nombre de client bacula en erreur : Sans Job cree depuis ou avec au moins un job en erreur dans les 24 dernieres heures"
			::= { baculaStats 3 } -- parent du sousObjet
		-- .1.3.6.1.4.1.33923.1.3 baculaTotalClients }}}
		-- {{{ .1.3.6.1.4.1.33923.1.4  baculaClientsTable
		baculaClientsTable			OBJECT-TYPE
			SYNTAX					SEQUENCE OF BaculaClientsEntry
			MAX-ACCESS				not-accessible
			STATUS					current
			DESCRIPTION				"table contenant tout les clients"
			::= { baculaStats 4 }
			-- {{{ .1.3.6.1.4.1.33923.1.4.1  baculaClientsEntry
			baculaClientsEntry			OBJECT-TYPE
				SYNTAX					BaculaClientsEntry
				MAX-ACCESS				not-accessible
				STATUS					current
				DESCRIPTION				"les entrees de la table"
				INDEX					{ baculaClientIndex }
				::= { baculaClientsTable 1 }
					BaculaClientsEntry			::= SEQUENCE {
						baculaClientIndex		CounterIndex,
						
						baculaClientName		DisplayString,
						baculaClientError		TrueFalse, 
						baculaClientSizeBackup		Counter64,
						baculaClientTotalSizeBackup	Integer32,
						baculaClientNumberFiles		Integer32,
						baculaClientTotalNumberFiles	Integer32
						
						}
				-- {{{ .1.3.6.1.4.1.33923.1.4.1.1 baculaClientsIndex
				baculaClientIndex		OBJECT-TYPE
					SYNTAX				CounterIndex
					MAX-ACCESS			not-accessible
					STATUS				current
					DESCRIPTION			"index de la table"
					::= { baculaClientsEntry 1 }
				--  .1.3.6.1.4.1.33923.1.4.1.1  baculaClientsIndex}}}
				-- {{{ .1.3.6.1.4.1.33923.1.4.1.2  baculaClientName
				baculaClientName		OBJECT-TYPE
					SYNTAX				DisplayString
					MAX-ACCESS			read-only
					STATUS				current
					DESCRIPTION			"Nom des clients"
					::= { baculaClientsEntry 2 }
				--  .1.3.6.1.4.1.33923.1.3.1.2  baculaClientName }}}
				-- {{{ .1.3.6.1.4.1.33923.1.4.1.3  baculaClientError
				baculaClientError		OBJECT-TYPE
					SYNTAX				TrueFalse
					MAX-ACCESS			read-only
					STATUS				current
					DESCRIPTION			"Client avec aucun job cree ou au moins un job en erreur dans les 24 heures"
					::= { baculaClientsEntry 3 }
				--  .1.3.6.1.4.1.33923.1.3.1.3  baculaClientError }}}
				-- {{{ .1.3.6.1.4.1.33923.1.4.1.4  baculaClientSizeBackup
				baculaClientSizeBackup		OBJECT-TYPE
					SYNTAX				Counter64
					MAX-ACCESS			read-only
					STATUS				current
					DESCRIPTION			"Taille de la sauvegarde sur les dernieres 24h"
					::= { baculaClientsEntry 4 }
				--  .1.3.6.1.4.1.33923.1.4.1.4  baculaClientSizeBackup }}}
				-- {{{ .1.3.6.1.4.1.33923.1.4.1.5  baculaClientTotalSizeBackup
				baculaClientTotalSizeBackup		OBJECT-TYPE
					SYNTAX				Integer32
					MAX-ACCESS			read-only
					STATUS				current
					DESCRIPTION			"Taille de la sauvegarde sur tout les jobs"
					::= { baculaClientsEntry 5 }
				--  .1.3.6.1.4.1.33923.1.4.1.5  baculaClientTotalSizeBackup }}}
				-- {{{ .1.3.6.1.4.1.33923.1.4.1.6 baculaClientNumberFiles
				baculaClientNumberFiles		OBJECT-TYPE
					SYNTAX				Integer32
					MAX-ACCESS			read-only
					STATUS				current
					DESCRIPTION			"Nombre de fichier sur les 24h"
					::= { baculaClientsEntry 6 }
				--  .1.3.6.1.4.1.33923.1.4.1.6  baculaClientNumberFiles }}}
				-- {{{ .1.3.6.1.4.1.33923.1.4.1.7 baculaClientTotalNumberFiles
				baculaClientTotalNumberFiles		OBJECT-TYPE
					SYNTAX				Integer32
					MAX-ACCESS			read-only
					STATUS				current
					DESCRIPTION			"Nombre de fichier de tout les jobs"
					::= { baculaClientsEntry 7 }
				--  .1.3.6.1.4.1.33923.1.4.1.7  baculaClientTotalNumberFiles }}}			
			--  .1.3.6.1.4.1.33923.1.4.1  baculaClientsEntry }}}
		--.1.3.6.1.4.1.33923.1.4  baculaClientsTable }}}		
	 --  .1.3.6.1.4.1.33923.1 baculaStats }}}
END
